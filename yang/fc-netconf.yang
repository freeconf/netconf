module fc-netconf {
	namespace "org.freeconf/restconf";
	prefix "nc";
    yang-version "1.1";

    container ssh {

        container options {
            leaf port {
                type string;
                default ":830";
            }

            leaf hostKeyFile {
                type string;
            }

            // Incredicibly basic implementaton, should eventually consider implementing
            //  https://www.ietf.org/archive/id/draft-ietf-netconf-keystore-29.html

            leaf adminUsername {
                description "To use a user name other than 'admin'";
                type string;
                default "admin";
            }

            leaf adminPassword {
                description "Clear text password to use for authenticating 'admin' login.";
                type string;
            }

            leaf adminKey {
                description "authorized public key string when no using password";
                type string;
            }
        }

        container status {
            config false;
            leaf running {
                type boolean;
            }            
        }
    }
}
